FME workspace 2018mapinfo2shp.fmw

Parameters:
- SourceDataset_MAPINFO = D:\FME_processing\test_fme\Lake_27_3.TAB   # Source MapInfo TAB File(s)
- FEATURE_TYPES = Lake_27_3
- DestDataset_ESRISHAPE = D:\FME_processing\test_fme\RESULT   # Destination Esri Shapefile Folder

Readers:
- MAPINFO_1: MAPINFO from $(SourceDataset_MAPINFO)

Writers:
- ESRISHAPE_1: ESRISHAPE to $(DestDataset_ESRISHAPE) in *XY-MT*

Lake_27_3 (reader MAPINFO_1)
    attributes: num integer, Зона char(254), MSK char(25), d20191106 char(18)
    -> GeometryFilter
GeometryFilter
    BREAK_AGG = Yes
    GEOM_PORT_NAMES = Point Line Arc Area Text
    INSTANTIATE = No
    POINT -> Lake_27_3 (writer ESRISHAPE_1)
    LINE -> Lake_27_300 (writer ESRISHAPE_1)
    ARC -> fme_feature_type arc (writer ESRISHAPE_1)
    AREA -> Lake_27_302 (writer ESRISHAPE_1)
    TEXT -> Lake_27_303 (writer ESRISHAPE_1)
Lake_27_3 (writer ESRISHAPE_1)
    attributes: num long, Зона char(254), MSK char(25), d20191106 char(18), fme_featur char(50)
Lake_27_300 (writer ESRISHAPE_1)
    attributes: num long, Зона char(254), MSK char(25), d20191106 char(18), fme_featur char(50)
fme_feature_type arc (writer ESRISHAPE_1)
    attributes: num long, Зона char(254), MSK char(25), d20191106 char(18), fme_featur char(50)
Lake_27_302 (writer ESRISHAPE_1)
    attributes: num long, Зона char(254), MSK char(25), d20191106 char(18), fme_featur char(50)
Lake_27_303 (writer ESRISHAPE_1)
    attributes: num long, Зона char(254), MSK char(25), d20191106 char(18), fme_featur char(50)
