FME workspace 2018mapinfo2mapinfo.fmw

Parameters:
- SourceDataset_MAPINFO = D:\FME_processing\test_fme\Lake_27_3.TAB   # Source MapInfo TAB File(s)
- FEATURE_TYPES =
- DestDataset_MAPINFO_4 = D:\FME_processing\test_fme\RESULT   # Destination MapInfo Folder

Readers:
- MAPINFO_1: MAPINFO from $(SourceDataset_MAPINFO)

Writers:
- MAPINFO_3: MAPINFO to $(DestDataset_MAPINFO_4) in *XY-MT*

Lake_27_3 (reader MAPINFO_1)
    attributes: num integer, Зона char(254), MSK char(25), d20191106 char(18)
    -> Lake_27_3 (writer MAPINFO_3)
Lake_27_3 (writer MAPINFO_3)
    attributes: num integer, Зона char(254), MSK char(25), d20191106 char(18)
