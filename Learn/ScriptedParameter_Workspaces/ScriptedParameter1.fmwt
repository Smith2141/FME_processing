FME workspace ScriptedParameter1.fmwt
Title: ScriptedParameter1
Description: Purpose
This workspace shows how to use the Python scripted type private parameter to allow grouping of layers (ie. feature types).
In this example, a choice (multiple) published parameter allows a user to select information they want. The user's selection is then converted to the appropriate feature types:
Layer Group -> Feature Type
Walking and Biking -> PublicStreets Bikeways
Rapid Transit -> RapidTransitLine RapidTransitStations
All Methods -> PublicStreets Bikeways RapidTransitLine RapidTransitStations
Requirements
FME Version 2017.1+
Usage
Select Run > Run with Prompt. Note the parameter
Open the Navigator > User Parameters > Private Parameters. Double click to view the definition of the parameter
Metadata
Requirements
ScriptedParameterData.dwg (attached)
History: 2011-01-10,Aaron Koning,Created,2017-10-05,DLeung,Updated,2018-01-17,DLeung,Updated source dataset format

Parameters:
- layers =   # "Walking and Biking"%"Rapid Transit"%"All Methods" Layers
- feature_types_to_read:   # Python Script
      import fme
      featureTypes = ''
      if fme.macroValues['layers'].find('Walking and Biking') != -1:
          featureTypes += 'PublicStreets Bikeways '
      if fme.macroValues['layers'].find('Rapid Transit') != -1:
          featureTypes += 'RapidTransitLine RapidTransitStations '
      if fme.macroValues['layers'].find('All Methods') != -1:
          featureTypes += 'PublicStreets Bikeways RapidTransitLine RapidTransitStations '
      #Debug
      #print featureTypes
      return featureTypes

Readers:
- ACAD_1: ACAD from $(FME_MF_DIR)1/dwg_olympic_venues_and_transportation/ScriptedParameterData.dwg

Note: Purpose / This workspace shows how to use the Python scripted type private parameter to allow grouping of layers (ie. feature types). / In this example, a choice (multiple) published parameter allows a user to select information they want. The user's selection is then converted to the appropriate feature types: / Layer Group -> Feature Type / Walking and Biking -> PublicStreets Bikeways / Rapid Transit -> RapidTransitLine RapidTransitStations / All Methods -> PublicStreets Bikeways RapidTransitLine RapidTransitStations / Requirements / FME Version 2017.1+ / Usage / Select Run > Run with Prompt. Note the parameter / Open the Navigator > User Parameters > Private Parameters. Double click to view the definition of the parameter / Metadata / Requirements / ScriptedParameterData.dwg (attached)
RapidTransitLine (reader ACAD_1)
    -> RapidTransitLine
RapidTransitLine: Inspector
Bikeways (reader ACAD_1)
    -> Bikeways
Bikeways: Inspector
PublicStreets (reader ACAD_1)
    -> PublicStreets
PublicStreets: Inspector
RapidTransitStations (reader ACAD_1)
    -> RapidTransitStations
RapidTransitStations: Inspector
