FME workspace ScriptedParameter2.fmwt
Title: ScriptedParameter2
Description: Purpose
This workspace shows how to use the Python scripted type private parameter to append the current date and time to an output dataset name to create a unique name.
In this example, a text published parameter allows a user to input the file name they want. The current date and time is then appended to the file name. This resulting text is then used to name the output dataset file with a linked parameter.
Requirements
FME 2017.1+
Usage
Select Run > Run with Prompt. Note the parameter
Open the Navigator > User Parameters > Private Parameters. Double click to view the definition of the parameter
Open the Navigator >Output [CSV2] > Feature Types > $(nameWithTime) >Parameters > General > CSV File Name. Note that it is linked to the private user parameter nameWithTime
Metadata
Requirements
DrinkingFountains.csv (attached)
Parks.tab (attached)
History: 2017-10-10,DLeung,Created,2017-12-19,DLeung,Updated with annoations,2018-02-08,DLeung,Updated workflow (added Tester)

Parameters:
- OutFileName = test   # Enter output dataset name
- DestDataset_CSV2 = C:\TEMP   # Destination CSV (Comma Separated Value) Folder
- nameWithTime:   # Python Script
      # Import fme module and datetime.datetime class
      import fme
      from datetime import datetime
      
      # Get the value of the published pararmeter
      OutFileName = fme.macroValues['OutFileName']
      
      # Use the now() method to get the current date and time
      # Format date as YYYYMMDD_HHMMSS with strftime method
      curTime = datetime.now().strftime("%Y%m%d_%H%M%S")
      
      # Concatenate the published parameter, an underscore, date time
      OutFileName = OutFileName + '_' + curTime
      
      # Return unique file name which becomes the value of the scripted parameter
      # This scripted parameter is linked to the destination dataset name
      return OutFileName

Readers:
- CSV2_1: CSV2 from $(FME_MF_DIR)1/Engineering/DrinkingFountains.csv in UTM83-10
- MITAB_1: MITAB from $(FME_MF_DIR)1/Parks/Parks.tab in UTM83-10

Writers:
- CSV2_2: CSV2 to $(DestDataset_CSV2)

Note: Purpose / This workspace shows how to use the Python scripted type private parameter to append the current date and time to an output dataset name to create a unique name. / In this example, a text published parameter allows a user to input the file name they want. The current date and time is then appended to the file name. This resulting text is then used to name the output dataset file with a linked parameter. / Requirements / FME 2017.1+ / Usage / Select Run > Run with Prompt. Note the parameter / Open the Navigator > User Parameters > Private Parameters. Double click to view the definition of the parameter / Open the Navigator >Output [CSV2] > Feature Types > $(nameWithTime) >Parameters > General > CSV File Name. Note that it is linked to the private user parameter nameWithTime / Metadata / Requirements / DrinkingFountains.csv (attached) / Parks.tab (attached)
DrinkingFountains (reader CSV2_1)
    attributes: FountainID string, Location string, Maintainer string, x_coord x_coordinate, y_coord y_coordinate
    -> PointOnAreaOverlayer [POINT]
Parks (reader MITAB_1)
    attributes: ParkId smallint, RefParkId smallint, ParkName char(40), NeighborhoodName char(40), EWStreet char(30), NSStreet char(30), DogPark char(1), Washrooms char(1), SpecialFeatures char(1)
    -> PointOnAreaOverlayer [AREA]
Note: PointOnAreaOverlayer / Find which drinking fountains fall / within parks / Parameters: / Overlap Count Attribute: _overlaps / Areas First: No / Aggregate Handling: Deaggregate / Attribute Accumulation: / Accumulation Mode: Merge Incoming / Conflict Resolution: Use Original
PointOnAreaOverlayer
    ATTR_ACCUM_MODE = Merge Incoming
    ATTR_CONFLICT_RES = Use Original
    POLYS_FIRST = No
    CANDIDATE_LIST_ATTRS_TO_INCLUDE_MODE = Selected Attributes
    DEAGGREGATE_INPUT = Yes
    OV_ATTR = _overlaps
    POINT -> Tester
    <REJECTED> -> Logger
Note: Tester / Tests for drinking fountains that / faill within a park (_overlaps is equal / or greater than 1)
Tester
    TEST_CLAUSE = TEST @Value(_overlaps) >= 1
    TEST_MODE = Automatic
    TEST_DESCRIPTION = ""
    BOOL_OP = OR
    PASSED -> AttributeManager
Note: AttributeManager / Remove attributes not required / Attribute Actions: / Input Attribute / Action / ParkId / Remove / RefParkId / Remove / EWStreet / Remove / NSStreet / Remove / Washrooms / Remove / SpecialFeatures / Remove / _overlaps / Remove
AttributeManager
    ATTR_TABLE:
      REMOVE ParkId
      REMOVE RefParkId
      REMOVE EWStreet
      REMOVE NSStreet
      REMOVE Washrooms
      REMOVE SpecialFeatures
      REMOVE _overlaps
    -> File1 (writer CSV2_2)
File1 (writer CSV2_2)
    attributes: FountainID string, Location string, Maintainer string, x_coord x_coordinate, y_coord y_coordinate, ParkName string, NeighborhoodName string, DogPark string
Logger
    MESSAGE = Feature is:
    MAXCOORDS = 20
    MAXFEATS = 20
