FME workspace PythonCaller4.fmwt
Title: PythonCaller4
Description: Purpose
This workspace shows how to use the PythonCaller transformer with a Python class to define a custom folder hierarchy for an output KML file.
In this example, the transformers within the Define Custom Folder Hierarchy bookmark defines custom folders using a concatenated string value of the 1st and 2nd level folder attributes for each feature. A UniqueValueLogger is used to find unique values of the 1st level attributes and 1st/2nd level concatenated attribute values. A PythonScript is used to assign KML atriibutes(kml_id, kml_name, and kml_parent). Each feature is emitted using the self.pyoutput(feature) method.
Output features are written to the Folder feature type of the KML writer. This writer create folders within the output KML dataset. 
Requirements
FME 2017.1+
Usage
Select Run. Ensure Run with Prompt is enabled.
Enter output KML dataset name.
Open the output KML Dataset within Google Earth. Note the custom folder hierarchy (by Neighbourhood and by Crime Type).
Metadata
Requirements
crime_json_2018_sampled.json (attached)
History: 03-26-2018,dleung,Created,03-28-2018,dleung,Updated annotations

Parameters:
- SourceDataset_GEOJSON = $(FME_MF_DIR)crime_json_2018_sampled.json   # Source GeoJSON File or URL
- TEXT = doc   # KML_Document Enter KML Document name
- DestDataset_OGCKML =   # Destination Google KML File

Readers:
- GEOJSON_1: GEOJSON from $(SourceDataset_GEOJSON)

Writers:
- OGCKML_1: OGCKML to $(DestDataset_OGCKML)

Note: Purpose / This workspace shows how to use the PythonCaller transformer with a Python class to define a custom folder hierarchy for an output KML file. / In this example, the transformers within the Define Custom Folder Hierarchy bookmark defines custom folders using a concatenated string value of the 1st and 2nd level folder attributes for each feature. A UniqueValueLogger is used to find unique values of the 1st level attributes and 1st/2nd level concatenated attribute values. A PythonScript is used to assign KML atriibutes(kml_id, kml_name, and kml_parent). Each feature is emitted using the self.pyoutput(feature) method. / Output features are written to the Folder feature type of the KML writer. This writer create folders within the output KML dataset. / Requirements / FME 2017.1+ / Usage / Select Run. Ensure Run with Prompt is enabled. / Enter output KML dataset name. / Open the output KML Dataset within Google Earth. Note the custom folder hierarchy (by Neighbourhood and by Crime Type). / Metadata / Requirements / crime_json_2018_sampled.json (attached)
Note: GeoJSON Reader
Crime 2018 (reader GEOJSON_1)
    attributes: TYPE string, YEAR int, MONTH string, DAY string, HOUR string, MINUTE string, HUNDRED_BLOCK string, NEIGHBOURHOOD string, X float, Y float
    -> GeometryRemover
    -> AttributeManager_2

Bookmark: Geographic Features
Note: Assign geographic features to appropriate folder / by setting kml_parent to the name of the folder
AttributeManager_2
    ATTR_TABLE:
      SET_TO kml_parent = @Value(TYPE);;@Value(NEIGHBOURHOOD)
      SET_TO kml_name = @Value(YEAR)@Value(MONTH)@Value(DAY) @Value(HOUR):@Value(MINUTE)
    -> 2018 Vancouver Crime (writer OGCKML_1)
Note: KML Writer
2018 Vancouver Crime (writer OGCKML_1)
    attributes: TYPE kml_char(255), YEAR kml_char(20), MONTH kml_char(255), DAY kml_char(255), HOUR kml_char(255), MINUTE kml_char(255), HUNDRED_BLOCK kml_char(255), NEIGHBOURHOOD kml_char(255), X kml_real64, Y kml_real64

Bookmark: Define Custom Folder Hierarchy
Note: Remove geometry for null features
GeometryRemover
    -> AttributeManager
Note: Create kml_document, kml_id, / kml_name attributes / Create a Neighbourhood/Crime Type / string with ';;' as delimiter for creating / KML folders
AttributeManager
    ATTR_TABLE:
      REMOVE MONTH
      REMOVE DAY
      REMOVE HOUR
      REMOVE MINUTE
      REMOVE HUNDRED_BLOCK
      REMOVE X
      REMOVE Y
      SET_TO kml_document = $(KML_Document)
      SET_TO NeighbourhoodTypeConcat = @Value(TYPE);;@Value(NEIGHBOURHOOD)
    -> UniqueValueLogger_2
    -> UniqueValueLogger
Note: Sort folders in alphabetical order
Sorter
    SORT_PARM = kml_name ALPHA ASCENDING
    SORTED -> Folder (writer OGCKML_1)
Note: Folder Feature Type KML Writer
Folder (writer OGCKML_1)

Bookmark: Define 1st Level Folders
Note: Find all unique Neighbourhood / values
UniqueValueLogger_2
    VAL = @Value(NEIGHBOURHOOD)
    -> PythonCaller_2
Note: Use Python to create features / for each unique Neighbourhood value / and assign kml_id, kml_name, and / kml_parent.
PythonCaller_2
    PYTHONSYMBOL = FeatureProcessor
    NEW_ATTRIBUTES = kml_id kml_name kml_parent kml_document
    PYTHONSOURCE:
      import fme
      import fmeobjects

      # Template Class Interface:
      # When using this class, make sure its name is set as the value of
      # the 'Class or Function to Process Features' transformer parameter
      class FeatureProcessor(object):
          def __init__(self):
              self.featureList = []
          def input(self,feature):
              self.featureList.append(feature)
          def close(self):
              for feature in self.featureList:
                  Attr = feature.getAttribute('_value')
                  feature.setAttribute("kml_id", Attr)
                  feature.setAttribute("kml_name", Attr)
                  #feature.setAttribute("kml_parent", fme.macroValues['KML_Document'])
                  self.pyoutput(feature)
    HIDE_ATTRIBUTES = _count _value
    -> Sorter

Bookmark: Define 2nd Level Folders
Note: Find all unique / Neighbourhood;;CrimeTypes / combinations
UniqueValueLogger
    VAL = @Value(NeighbourhoodTypeConcat)
    -> PythonCaller
Note: Use Python to create features / for each unique Neighbourhood Crime Type / combo and assign kml_id, kml_name, and / kml_parent.
PythonCaller
    PYTHONSYMBOL = FeatureProcessor
    NEW_ATTRIBUTES = kml_id kml_name kml_parent kml_document
    PYTHONSOURCE:
      import fme
      import fmeobjects

      # Template Class Interface:
      # When using this class, make sure its name is set as the value of
      # the 'Class or Function to Process Features' transformer parameter
      class FeatureProcessor(object):
          def __init__(self):
              self.featureList = []
          def input(self,feature):
              self.featureList.append(feature)
          def close(self):
              for feature in self.featureList:
                  listAttr = feature.getAttribute('_value')
                  feature.setAttribute("kml_id", listAttr)
                  feature.setAttribute("kml_name", listAttr.rpartition(';;')[0])
                  feature.setAttribute("kml_parent", listAttr.rpartition(';;')[-1])
                  self.pyoutput(feature)
    HIDE_ATTRIBUTES = _value _count
    -> Sorter

FME custom transformer UniqueValueLogger
This transformer lists all of the unique values for a chosen attribute. A count of the number of occurrences of each unique value is also displayed. The information is both logged in the Translation Window / workspace .log file, and stored in attributes.
This transformer is useful when you are creating a workspace and need to know the possible values to use in a filter.
Input Ports
    Input 
This transformer accepts any features with an attribute.
    Output Ports
    Output
Features are output with new attributes containing the number of occurrences of each unique value.
_count: Number of occurrences of each unique value.
_value: Unique values of selected attribute.
    Parameters
    Attribute to Analyze
Select the attribute for the transformer to run analysis on.

Parameters:
- VAL =   # Attribute to Analyze

Input (input)
    -> AttributeCreator

Bookmark: Count and log unique attribute values
AttributeCreator
    ATTR_TABLE = SET_TO _log_candidate = $(VAL)
    -> AttributeKeeper
Note: Remove unwanted / attributes
AttributeKeeper
    KEEP_ATTRS = _log_candidate
    -> Aggregator
Note: Create aggregates of / features, grouped by / the target attribute value
Aggregator
    COUNT_ATTR = _count
    SEP = ,
    ACCUM_ATTRS_NAME = Yes
    MODE = Geometry - Assemble One Level
    AGGREGATE_TYPE = Homogeneous Collection (If Possible)
    GROUP_BY = _log_candidate
    ORDERED = No
    AGGREGATE -> StringConcatenator
Note: Concatenate unique values / with their occurrence counts
StringConcatenator
    PARM_LINE = "@Value(_count),@Value(_log_candidate)\n"
    ACTION = Create New Attribute
    VAL_ATTR = _concatenated
    -> Sorter
Note: Sort output based on / occurrence count and / attribute value
Sorter
    SORT_PARM = _count NUMERIC DESCENDING _log_candidate ALPHA ASCENDING
    SORTED -> ListBuilder
    SORTED -> AttributeManager
Note: Turn all input features / Into a single list
ListBuilder
    LIST_NAME = _list
    -> ListConcatenator
Note: Concatenate values of / the list into an attribute
ListConcatenator
    DROP_EMPTY_PARTS = No
    LIST_ATTR = _list{}._concatenated
    VAL_ATTR = UNIQUE VALUES
    -> StringConcatenator_2
Note: Add header
StringConcatenator_2
    PARM_LINE = "\n\nCOUNT,VALUE\n@Value(UNIQUE VALUES)\n"
    ACTION = Create New Attribute
    VAL_ATTR = UNIQUE VALUES
    -> AttributeRemover_2
Note: Remote the list
AttributeRemover_2
    LIST_ATTRS = _list{}
    -> Logger
Note: Log the single feature / that contains the / output attribute
Logger
    MAXFEATS = 1
    MESSAGE = Unique values:
    MAXCOORDS = 1

Bookmark: Create output
AttributeManager
    ATTR_TABLE:
      RENAME_SET_VALUE _log_candidate > _value
      REMOVE _concatenated
    -> Output (output)
Output (output)
