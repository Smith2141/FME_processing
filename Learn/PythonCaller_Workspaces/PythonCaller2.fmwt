FME workspace PythonCaller2.fmwt
Title: PythonCaller2
Description: Purpose
This workspace shows how the PythonCaller transformer is used within a custom transformer to compare strings.
In this example, the FuzzyStringComparer custom transformer is used to compare two strings. One of the transformer within the FuzzyStringComparer is a PythonCaller trasformer. The user will look the script within the PythonCaller to see how a Python function and a module from the standard Python library can be used perform operations that a standard transformer may not be able to do.
Requirements
FME 2017.1+
Usage
Run the workspace. The output will open in the Data Inspector. Look at the ratioCompare attribute
Select the FuzzyStringComparer custom transformer. Right-click the transformer and select Edit.
Open the PythonCaller transformer. Note the function name entered in Class or Function to Process Features and the attribute name in Attributes to Expose
Veiw the script. It uses difflib module to caculate the similarity ratio.
Metadata
Requirements
PublicTrees.csv (attached)

Parameters:
- SourceDataset_CSV2 = $(FME_MF_DIR)1/Parks/PublicTrees.csv   # Source CSV (Comma Separated Value) File(s)

Readers:
- CSV2_1: CSV2 from $(SourceDataset_CSV2)

Note: Purpose / This workspace shows how the PythonCaller transformer is used within a custom transformer to compare strings. / In this example, the FuzzyStringComparer custom transformer is used to compare two strings. One of the transformer within the FuzzyStringComparer is a PythonCaller trasformer. The user will look the script within the PythonCaller to see how a Python function and a module from the standard Python library can be used perform operations that a standard transformer may not be able to do. / Requirements / FME 2017.1+ / Usage / Run the workspace. The output will open in the Data Inspector. Look at the ratioCompare attribute / Select the FuzzyStringComparer custom transformer. Right-click the transformer and select Edit. / Open the PythonCaller transformer. Note the function name entered in Class or Function to Process Features and the attribute name in Attributes to Expose / Veiw the script. It uses difflib module to caculate the similarity ratio. For more details, please see the tutorial page for the PythonCaller transformer. / Metadata / Requirements / PublicTrees.csv (attached)
CSV (reader CSV2_1)
    attributes: TreeID string, Address string, Neighborhood string, Height string, Diameter string, PlantingDate string, Cultivar string, Genus string, Species string, CommonName string, CommonName2 string
    -> AttributeManager
Note: Add attribute for similarity ratio
AttributeManager
    ATTR_TABLE = SET_TO ratioCompare
    -> FuzzyStringComparer
FuzzyStringComparer
    STRING2 = @Value(CommonName2)
    STRING1 = @Value(CommonName)
    DEST_ATTR = ratioCompare
    -> FuzzyStringComparer_Output
FuzzyStringComparer_Output: Inspector

FME custom transformer FuzzyStringComparer
This transformer uses the Python difflib module to compare two string attributes and calculate a similarity ratio. The similarity ratio describes the closeness of the match between the two strings. The higher the value, the closer the match (1 = exact).
If desired, the transformer will also output a comparison string. This is a two line string illustrating the differences between the two input strings by lining up the matching sections. When displaying the comparison string, you will get the best results using a non-proportional font like Courier.
Example:
string 1 = 'South Dayton Street'
string 2 = 'S Dayton St.'
The comparison string would be:
South Dayton St reet
S        Dayton St.
Input Ports 
Input - This transformer will accept any feature containing attributes to compare.
Output Ports 
Output - Features are output with a new attribute added to store the calculated comparison ratio value.
Parameters 
String 1 Attribute - The name of the attribute containing the first string to compare.
String 2 Attribute - The name of the attribute containing the second string to compare.
Output Ratio Attribute - A text field to set the name of the attribute that will be created to store the calculated ratio value. 
Output Comparison Attribute- An optional text field to set the name of the attribute that will be created to store the comparison string.

Parameters:
- STRING1 =   # String 1 Attribute
- STRING2 =   # String 2 Attribute
- DEST_ATTR =   # Output Ratio Attribute
- DEST_COMP =   # Output Comparison Atttribute

Input (input)
    -> AttributeCreator
Note: Initialize attributes
AttributeCreator
    ATTR_TABLE:
      SET_TO FuzzyStringCompare.string1 = $(STRING1)
      SET_TO FuzzyStringCompare.string2 = $(STRING2)
    -> PythonCaller
Note: Calculate similarity ratio
PythonCaller
    NEW_ATTRIBUTES = FuzzyStringCompare.ratio
    PYTHONSYMBOL = FuzzyStringCompare
    PYTHONSOURCE:
      import difflib
      import sys

      def FuzzyStringCompare(feature):
          # get strings from attributes
          string1 = feature.getAttribute('FuzzyStringCompare.string1')
          string2 = feature.getAttribute('FuzzyStringCompare.string2')
          version = sys.version_info[0]

          if string1 != None and string2 != None:
              # convert to unicode strings if necessary
              if version > 2:
                  if not isinstance(string1, str):
                      string1 = '{}'.format(string1)
                  if not isinstance(string2, str):
                      string2 = '{}'.format(string2)
              else:
                  if not isinstance(string1, unicode):
                      string1 = u'{}'.format(string1)
                  if not isinstance(string2, unicode):
                      string2 = u'{}'.format(string2)

              # calculate difference ratio
              s = difflib.SequenceMatcher(None,string1.lower(),string2.lower())
              ratio = s.ratio()

              # update input strings
              differ = difflib.ndiff(string1,string2)
              diff1 = ''
              diff2 = ''
              for line in differ:
                  if line[0] == '-':
                      diff1 = diff1 + (line[2])
                      diff2 = diff2 + ' '
                  elif line[0] == '+':
                      diff1 = diff1 + ' '
                      diff2 = diff2 + (line[2])
                  else:
                      diff1 = diff1 + (line[2])
                      diff2 = diff2 + (line[2])

              # set new attributes on feature
              feature.setAttribute('FuzzyStringCompare.ratio',ratio)
              feature.setAttribute('FuzzyStringCompare.string1',diff1)
              feature.setAttribute('FuzzyStringCompare.string2',diff2)
    -> AttributeCreator_2
Note: Set output ratio attribute name
AttributeCreator_2
    ATTR_TABLE = SET_TO $(DEST_ATTR) = @Value(FuzzyStringCompare.ratio)
    -> Tester
Note: If comparison name set, / add comparison string
Tester
    TEST_CLAUSE = TEST $(DEST_COMP) NOT_ATTRIBUTE_HAS_VALUE ""
    TEST_DESCRIPTION = ""
    TEST_MODE = Automatic
    BOOL_OP = OR
    PASSED -> AttributeRemover
    FAILED -> AttributeCreator_3
AttributeCreator_3
    ATTR_TABLE:
      SET_TO $(DEST_COMP) = @Value(FuzzyStringCompare.string1)
        @Value(FuzzyStringCompare.string2)
    -> AttributeRemover
Note: Clean up temporary attributes.
AttributeRemover
    REMOVE_ATTRS = FuzzyStringCompare.ratio,FuzzyStringCompare.string1,FuzzyStringCompare.string2
    -> Output (output)
Output (output)
