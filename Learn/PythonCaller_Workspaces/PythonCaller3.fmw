FME workspace PythonCaller3.fmw
Title: Total Feature Area Calculator
Description: Purpose
This workspace shows how to use the PythonCaller transformer with a Python class to calculate the area of all features.
In this example, the Creator transformer creates features, then the PythonCaller transformer calls a class that calculates the area of all features by looping through the features and add the current feature's area to the running total. The final area value is assigned to a new attribute called total_area. The attribute output is displayed in the Translation Log pane.
Note: The same task can be done with standard FME transformers.
Requirements
FME 2017.1+
Usage
Select Run. Note in the total_area attribute in the Translation Log pane
Open the Creator transformer and increase the number of features
Run the workspace again and note the increase in the total_area attribute value
Metadata
Requirements
None
History: Unknown,Unknown,Created FME 2012,2017-10-10,DLeung,Updated,2018-02-06,DLeung,Updated. Added transformer annotations.

Note: Purpose / This workspace shows how to use the PythonCaller transformer with a Python class to calculate the area of all features. / In this example, the Creator transformer creates features, then the PythonCaller transformer calls a class that calculates the area of all features by looping through the features and add the current feature's area to the running total. The final area value is assigned to a new attribute called total_area. The attribute output is displayed in the Translation Log pane. / Note: The same task can be done with standard FME transformers. / Requirements / FME 2017.1+ / Usage / Select Run. Note in the total_area attribute in the Translation Log pane / Open the Creator transformer and increase the number of features / Run the workspace again and note the increase in the total_area attribute value / Metadata / Requirements / None
Note: Creator [Creator] / Parameters: / Geometry Source: Geometry Object / Geometry Object: Polygon / Coordinate System: <not set> / Number to Create: 1 / Create At End: No / Creation Instance Attribute: _creation_instance
Creator
    GEOM = <?xml version="1.0" encoding="US_ASCII" standalone="no" ?><geometry><polygon><line><coord x="0" y="0"/><coord x="1" y="1"/><coord x="2" y="0"/><coord x="1" y="-1"/><coord x="0" y="0"/></line></polygon></geometry>
    NUM = 1
    GEOMTYPE = Geometry Object
    CREATED -> PythonCaller
Note: PythonCaller [PythonCaller] / Parameters: / Python Script: / import fme / import fmeobjects / class FeatureProcessor(object): / def __init__(self): / self.featureList = [] / self.totalArea = 0.0 / def input(self,feature): / self.featureList.append(feature) / self.totalArea += feature.getGeometry().getArea() / def close(self): / for feature in self.featureList: / feature.setAttribute("total_area", self.totalArea) / self.pyoutput(feature) / Class or Function to Process Features: FeatureProcessor / Advanced: / Attributes to Expose: total_area / Attributes To Hide: <not set> / Lists to Hide: <not set>
PythonCaller
    PYTHONSOURCE:
      import fme
      import fmeobjects

      # Template Class Interface:
      # When using this class, make sure its name is set as the value of
      # the 'Class or Function to Process Features' transformer parameter
      class FeatureProcessor(object):
          def __init__(self):
              self.featureList = []
              self.totalArea = 0.0
          def input(self,feature):
              self.featureList.append(feature)
              self.totalArea += feature.getGeometry().getArea()
          def close(self):
              for feature in self.featureList:
                  feature.setAttribute("total_area", self.totalArea)
                  self.pyoutput(feature)
    PYTHONSYMBOL = FeatureProcessor
    NEW_ATTRIBUTES = total_area
    -> Logger
Logger
    MESSAGE = Feature is:
    MAXCOORDS = 20
    MAXFEATS = 20
