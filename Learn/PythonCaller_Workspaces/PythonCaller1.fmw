FME workspace PythonCaller1.fmw
Title: Date Time Attribute with Python
Description: Purpose
This workspace shows how to use the PythonCaller transformer with a Python function to add a date and time attribute to the features created.
In this example, the Creator transformer creates features, then the PythonCaller transformer calls a function that gets the current date and time. The date and time then assigned to a new attribute called 'timestamp'. The attribute output is displayed in the Translation Log window.
Note: The same task can be done with the DateTimeStamper transformer.
Requirements
FME 2017.1+
Usage
Select Run. Note in the 'timestamp' attribute in the Translation Log pane
Open the PythonCaller transformer. Note the function name entered in Class or Function to Process Features and the attribute name in Attributes to Expose
Metadata
Requirements
None
History: Unknown,Unknown,Created (FME 2012),2017-10-10,DLeung,Updated,2018-02-06 ,DLeung,Updated to add PythonCaller annotations

Note: Purpose / This workspace shows how to use the PythonCaller transformer with a Python function to add a date and time attribute to the features created. / In this example, the Creator transformer creates features, then the PythonCaller transformer calls a function that gets the current date and time. The date and time then assigned to a new attribute called 'timestamp'. The attribute output is displayed in the Translation Log window. / Note: The same task can be done with the DateTimeStamper transformer. / Requirements / FME 2017.1+ / Usage / Select Run. Note in the 'timestamp' attribute in the Translation Log pane / Open the PythonCaller transformer. Note the function name entered in Class or Function to Process Features and the attribute name in Attributes to Expose / Metadata / Requirements / None
Creator
    GEOMTYPE = Geometry Object
    NUM = 5
    CREATED -> PythonCaller
Note: PythonCaller [PythonCaller] / Parameters: / Python Script: / import fmeobjects / import time / # Template Function interface: / def timestampFeature(feature): / curTime = time.ctime(time.time()) / feature.setAttribute("timestamp",curTime) / Class or Function to Process Features: timestampFeature / Advanced: / Attributes to Expose: timestamp / Attributes To Hide: <not set> / Lists to Hide: <not set>
PythonCaller
    PYTHONSYMBOL = timestampFeature
    NEW_ATTRIBUTES = timestamp
    PYTHONSOURCE:
      import fmeobjects
      import time

      # Template Function interface:

      def timestampFeature(feature):
          curTime = time.ctime(time.time())
          feature.setAttribute("timestamp",curTime)
    -> Logger
Logger
    MAXCOORDS = 20
    MAXFEATS = 20
    MESSAGE = Feature is:
