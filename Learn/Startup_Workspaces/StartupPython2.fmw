FME workspace StartupPython2.fmw
Title: MessageToLogFile
Description: Purpose
This workspace shows how to use the  Startup Python Script function to add a custom (user-defined) message to the log file.
See the startup Python script in the Navigator pane: Workspace Parameters > Scripting for the Python Script
Requirements
FME 2017.1.+
Usage
Select Run> Run Workspace or F5
Look at the Translation Log pane. Note that both the custom message and the print function message appears.
Go to where the workspace is saved to access the log file. Log file should have same name as workspace but with a log file extension.
Open with text editor. Note that the custom message is saved but not the print function message.
Metadata
Data Requirement
none
History: 2017-10-12DLeung,DLeung,Created (2017.1.1)
Startup Python:
      # Import FME Objects module
      import fmeobjects

      # Create FME Log File object name called logger
      logger = fmeobjects.FMELogFile()

      # Call logMessageString method to add custom text
      logger.logMessageString("You can add custom text to the log file")

      # Demonstrates print statement will only print to log pane
      print('This will only print to the Translation Log pane')

Parameters:
- DestDataset_XLSXW = C:\temp\output.xls   # Destination Microsoft Excel File

Writers:
- XLSXW_1: XLSXW to $(DestDataset_XLSXW)

Note: Purpose / This workspace shows how to use the Startup Python Script function to add a custom (user-defined) message to the log file. / See the startup Python script in the Navigator pane: Workspace Parameters > Scripting for the Python Script / Requirements / FME 2017.1+ / Usage / Select Run> Run Workspace or F5 / Look at the Translation Log pane. Note that both the custom message and the print function message appears. / Go to where the workspace is saved to access the log file. Log file should have same name as workspace but with a log file extension. / Open with text editor. Note that the custom message is saved but not the print function message. / Metadata / Data Requirement / none
Note: Creator [Creator] / Parameters: / Geometry Source: Geometry Object / Geometry Object: Null / Coordinate System: <not set> / Number to Create: 1 / Create At End: No / Creation Instance Attribute: _creation_instance
Creator
    GEOMTYPE = Geometry Object
    NUM = 1
    CREATED -> DateTimeStamper
Note: DateTimeStamper [DateTimeStamper] / Parameters: / Type: Datetime / Time Zone: Local / UTC Offset: No / Result Attribute: _timestamp
DateTimeStamper
    STAMP_TYPE = datetime
    TIMEZONE = local
    DATETIME_ATTR = _timestamp
    INCLUDE_OFFSET = NO
    -> MyWorkSheet (writer XLSXW_1)
MyWorkSheet (writer XLSXW_1)
    attributes: Time auto(20)
