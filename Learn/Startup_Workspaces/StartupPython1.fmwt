FME workspace StartupPython1.fmwt
Title: StartupPython1
Description: Purpose
This workspace shows how to use the Startup Python Script function to create a zip file backup of the source dataset to the workspace location.
Look at the startup Python script in the Navigator pane: Workspace Parameters > Scripting
    Requirements
FME 2017.1+
    Usage
    Select Run> Run Workspace or F5
    Go to the C:\TEMP folder. A zipped file of the source dataset should have been created with the the dataset name and the text '_backup' in the name.
    Metadata 
    Data Requirement
legal_lot_numbers.shp (attached)
History: 2017-10-19,DLeung,Created (2017.1.1),2018-01-09,DLeung,Updated script, added annotations
Startup Python:
      # import fme and shutil modules
      import fme, shutil
      from os import path

      # Filepath hardcoded to C:\TEMP
      workspacePath = 'C:\\TEMP'
      # Filepath of source dataset using macroValues dictionary
      sourceFile = fme.macroValues['SourceDataset_ESRISHAPE']

      # Gets dataset name without extension with '_backup' appended
      sourceName = path.splitext(path.basename(sourceFile))[0] + '_backup'

      # Path of new zip with name
      zipDir = '{}\\{}'.format(workspacePath,sourceName)

      # Root directory of folder containing source dataset
      sourcePath = path.dirname(sourceFile)

      # If zip file with same name already exists, do not create, add message to log window
      if path.exists(zipDir + '.zip'):
          # Message to log window
          print(zipDir + '.zip already exists. Did not create zip.')
      else:
          # Use shutil module to create zip file
          shutil.make_archive(zipDir, 'zip', sourcePath)
          print('Created backup of ' + path.basename(sourceFile))
          print('Path at ' + zipDir + '.zip')

      # Debugging
      # print(sourceName)
      # print(zipDir)

Parameters:
- SourceDataset_ESRISHAPE = $(FME_MF_DIR)1/Startup1Data/legal_lot_numbers.shp   # Source Esri Shapefile(s)
- DestDataset_GML = C:\TEMP\Output\Startup1.gml   # Destination Geography Markup Language (GML) File

Readers:
- ESRISHAPE_1: ESRISHAPE from $(SourceDataset_ESRISHAPE)

Writers:
- GML_1: GML to $(DestDataset_GML)

Note: Purpose / This workspace shows how to use the Startup Python Script function to create a zip file backup of the source dataset to the workspace location. / Look at the startup Python script in the Navigator pane: Workspace Parameters > Scripting / Requirements / FME 2017.1+ / Usage / Select Run> Run Workspace or F5 / Go to the C:\TEMP folder. A zipped file of the source dataset should have been created with the the dataset name and the text '_backup' in the name. / Metadata / Data Requirement / legal_lot_numbers.shp (attached)
legal_lot_numbers (reader ESRISHAPE_1)
    attributes: OBJECTID long, LOT_NUMBER char(30)
    -> Reprojector
Note: Reprojector / Source Coordinate System: Read from feature / Destination Coordinate System: LL-WGS84
Reprojector
    RASTER_CELL_SIZE = Preserve Cells
    SOURCE = Read from feature
    INTERPOLATION_TYPE_NAME = Nearest Neighbor
    DEST = LL-WGS84
    REPROJECTED -> legal_lot_numbers (writer GML_1)
legal_lot_numbers (writer GML_1)
    attributes: OBJECTID xml_int32, LOT_NUMBER xml_char(30)
