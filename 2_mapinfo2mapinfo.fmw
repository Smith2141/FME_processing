FME workspace 2_mapinfo2mapinfo.fmw

Parameters:
- SourceDataset_MAPINFO = C:\LAYER_T\51_01_0000000.TAB   # Source MapInfo TAB File(s)
- FEATURE_TYPES =
- Out_name =
- DestDataset_MAPINFO = C:\LAYER_T\RES   # Destination MapInfo Folder

Readers:
- MAPINFO_1: MAPINFO from $(SourceDataset_MAPINFO)

Writers:
- MAPINFO_2: MAPINFO to $(DestDataset_MAPINFO)

51_01_0000000_Parcel (reader MAPINFO_1)
    attributes: AccNumberZ char(181), AccountNum char(181), Area char(181), CadCost char(181), Category char(181), Coord_Name char(181), Utilizatio char(181), ByDoc char(181), Block_KN char(181), Parcel_KN char(181), Parcel_St char(181), SnglUseKN char(181), Sub_Num char(181), BoundName char(181), GeomType char(181), XmlFile char(181)
    -> Reprojector
Reprojector
    DEST = *XY-MT*
    INTERPOLATION_TYPE_NAME = Nearest Neighbor
    RASTER_CELL_SIZE = Preserve Cells
    RASTER_TOLERANCE = 0.0
    SOURCE = Read from feature
    REPROJECTED -> fme_feature_type_1 (writer MAPINFO_2)
fme_feature_type_1 (writer MAPINFO_2)
    attributes: AccNumberZ char(181), AccountNum char(181), Area char(181), CadCost char(181), Category char(181), Coord_Name char(181), Utilizatio char(181), ByDoc char(181), Block_KN char(181), Parcel_KN char(181), Parcel_St char(181), SnglUseKN char(181), Sub_Num char(181), BoundName char(181), GeomType char(181), XmlFile char(181)
