FME workspace 3_mif2shape_by_geom_type.fmw
Title: PolygonBuilder

Parameters:
- SourceDataset_MIF = C:\LAYER_T_RES\Lake_27_3.MIF   # Source MapInfo MIF/MID File(s)
- FEATURE_TYPES =   # " " Feature Types to Read
- DestDataset_ESRISHAPE = C:\fme_test_mif_to_shp\Output   # Destination Esri Shapefile Folder
- SourceDataset_MAPINFO = C:\fme_test_mif_to_shp\Pointstab.TAB   # Source MapInfo TAB File(s)
- FEATURE_TYPES_2 = Pointstab

Readers:
- MIF_1: MIF from $(SourceDataset_MIF)
- MAPINFO_1: MAPINFO from $(SourceDataset_MAPINFO)

Writers:
- ESRISHAPE_1: ESRISHAPE to $(DestDataset_ESRISHAPE)

PointCloudCombiner
    ACCUM_ATTRS_NAME = Yes
    EXTRACT_RASTER_NODATA_NAME = No
    SPACING = 1.0
    -> Shapefile10000 (writer ESRISHAPE_1)
LineBuilder
    ACCUM_INPUT_ATTRS = Use Attributes From One Feature
    GROUP_BY = fme_feature_type
    REMOVE_DUPLICATES = No
    LINE -> Shapefile100 (writer ESRISHAPE_1)
AreaBuilder
    ALLOW_CYCLES = No
    CHECK_CURVE_DIRECTION = No
    CONNECT_Z_MODE = First Wins
    CONSIDER_NODE_ELEVATION = no
    DONUT_CREATION = YES
    DROP_HOLES = No
    GROUP_BY = fme_basename
    LINES_AS_SEGMENTS = No
    POLY_ACCUM_ATTRS_NAME = Use Attributes From One Feature
    SNAPTYPE_PARAM = None
    AREA -> Shapefile1 (writer ESRISHAPE_1)
Note: This workspace takes .MIF files from a folder and transforms them into Shapefiles. This workspace will be run using the WorkspaceRunner transformer in the WorkspaceRunner.fmw workspace
TextAdder
    KEEP_GEOM = Yes
    TEXT_ROTATION = 0
    TEXT_SIZE = @Value(mapinfo_text_fontsize)
    TEXT_STRING = @Value(mapinfo_text_string)
    -> Shapefile1000000 (writer ESRISHAPE_1)

Bookmark: Source Data
imp_Lake_27_3 (reader MAPINFO_1)
    attributes: AccNumberZ char(181), AccountNum char(181), Area char(181), CadCost char(181), Category char(181), Coord_Name char(181), Utilizatio char(181), ByDoc char(181), Block_KN char(181), Parcel_KN char(181), Parcel_St char(181), SnglUseKN char(181), Sub_Num char(181), BoundName char(181), GeomType char(181), XmlFile char(181)
    -> GeometryFilter

Bookmark: Optional: Data Manipulation
GeometryFilter
    BREAK_AGG = Yes
    GEOM_PORT_NAMES = Point Line Area Text "Point Cloud"
    INSTANTIATE = Yes
    POINT -> PointCloudCombiner
    AREA -> AreaBuilder
    LINE -> LineBuilder
    TEXT -> TextAdder

Bookmark: Output Data Type
Note: Write out to Shapefile, set the Shapefile name to fme_basename to fanout the data.
Shapefile10000 (writer ESRISHAPE_1)
    attributes: AREA double, BLOCK_ID char(2), FLAG double, LOT char(2), LU90 double, LUCODE double, PLAT char(6), LU95 double, LULU double, SOURCE char(10), PERIMETER double, PARCEL_ID char(23), mif_brush_ long, mif_brus00 long, mif_brus01 short
Note: Write out to Shapefile, set the Shapefile name to fme_basename to fanout the data.
Shapefile100 (writer ESRISHAPE_1)
    attributes: AREA double, BLOCK_ID char(2), FLAG double, LOT char(2), LU90 double, LUCODE double, PLAT char(6), LU95 double, LULU double, SOURCE char(10), PERIMETER double, PARCEL_ID char(23), mif_brush_ long, mif_brus00 long, mif_brus01 short
Note: Write out to Shapefile, set the Shapefile name to fme_basename to fanout the data.
Shapefile1 (writer ESRISHAPE_1)
    attributes: AREA double, BLOCK_ID char(2), FLAG double, LOT char(2), LU90 double, LUCODE double, PLAT char(6), LU95 double, LULU double, SOURCE char(10), PERIMETER double, PARCEL_ID char(23), mif_brush_ long, mif_brus00 long, mif_brus01 short
Note: Write out to Shapefile, set the Shapefile name to fme_basename to fanout the data.
Shapefile1000000 (writer ESRISHAPE_1)
    attributes: AREA double, BLOCK_ID char(2), FLAG double, LOT char(2), LU90 double, LUCODE double, PLAT char(6), LU95 double, LULU double, SOURCE char(10), PERIMETER double, PARCEL_ID char(23), mif_brush_ long, mif_brus00 long, mif_brus01 short
